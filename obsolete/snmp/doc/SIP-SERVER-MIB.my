SIP-SERVER-MIB DEFINITIONS ::= BEGIN    
       
   IMPORTS    
        MODULE-IDENTITY,    
        OBJECT-TYPE,    
        Counter32,    
        Integer32,    
        Unsigned32,  
        Gauge32,  
        mib-2  
             FROM SNMPv2-SMI    
       
        RowStatus,    
        TruthValue,   
        TimeStamp, DateAndTime    
             FROM SNMPv2-TC    
       
        MODULE-COMPLIANCE,    
        OBJECT-GROUP    
             FROM SNMPv2-CONF    
       
        SnmpAdminString    
             FROM SNMP-FRAMEWORK-MIB    
            
        applIndex    
             FROM NETWORK-SERVICES-MIB  
  
        InetAddressType,   
        InetAddress  
             FROM INET-ADDRESS-MIB;  
       
   sipServerMIB MODULE-IDENTITY    
        LAST-UPDATED   "200202040000Z"    
        ORGANIZATION   "IETF SIP Working Group, SIP MIB Team"    
        CONTACT-INFO    
                "SIP MIB email: sip@ietf.org 
       
                 Co-editor  Kevin Lingle    
                            Cisco Systems, Inc.    
                 postal:    7025 Kit Creek Road    
                            P.O. Box 14987    
     
   

   
    
                            Research Triangle Park, NC 27709    
                            USA    
                 email:     klingle@cisco.com    
                 phone:     +1 919 392 2029    
  
                 Co-editor  Joon Maeng    
                            ipDialog, Inc.  
                 postal:    7701 N. Lamar Blvd., Suite 304  
                            Austin, TX 78752-1023  
                            USA    
                 email:     jmaeng@ipdialog.com    
                 phone:     +1 512 371 1770         
  
                 Co-editor  Dave Walker    
                            SS8 Networks, Inc.    
                 postal:    495 March Road   
                            Kanata, ON K2K 3G1   
                            Canada    
                 email:     drwalker@ss8.com    
                 phone:     +1 613 592 2100   
   
                 Co-editor  Jean-Francois Mule    
                            CableLabs    
                 postal:    400 Centennial Parkway    
                            Louisville, CO 80027    
                            USA    
                 email:     jf.mule@cablelabs.com    
                 phone:     +1 303 661 3708  " 
        DESCRIPTION    
                "Initial version of Session Initiation Protocol (SIP)    
                 Server MIB module.    
       
                 SIP is an application-layer signalling protocol for     
                 creating, modifying and terminating multimedia     
                 sessions with one or more participants. These sessions    
                 include 
                 telephone calls.  SIP is defined in RFC 2543 (March     
                 1999).    
       
                 This MIB is defined for the management of SIP Proxy,     
                 Redirect, and Registrar Servers.    
       
                 A Proxy Server acts as both a client and a server.    
                 It accepts requests from other clients, either    
                 responding to them or passing them on to other    
                 servers, possibly after modification.    
       
                 A Redirect Server accepts requests from clients and    
                 returns zero or more addresses to that client. 
                 Unlike a User Agent Server it does not accept calls.   
   
                 A Registrar is a server that accepts REGISTER    
                 requests.  A Registrar is typically co-located with a    
                 Proxy or Redirect Server."    
        ::= { mib-2 9991 }  -- to be assigned by IANA  
  
 
     
   

   
    
   -- Top-Level Components of this MIB.       
   sipServerMIBObjects  OBJECT IDENTIFIER ::= { sipServerMIB 1 }  
   sipServerMIBConform  OBJECT IDENTIFIER ::= { sipServerMIB 2 }  
       
   --    
   -- These groups contains objects common to all SIP servers.  
   --    
   sipServerCfg         OBJECT IDENTIFIER ::= { sipServerMIBObjects 1 }    
   sipServerStats       OBJECT IDENTIFIER ::= { sipServerMIBObjects 2 }    
       
   --    
   -- Common Server Configuration Objects    
   --    
   sipServerCfgTable OBJECT-TYPE    
       SYNTAX     SEQUENCE OF SipServerCfgEntry    
       MAX-ACCESS not-accessible    
       STATUS     current    
       DESCRIPTION    
            "This table contains configuration objects applicable    
             to SIP redirect and proxy servers."  
       ::= { sipServerCfg 1 }    
       
   sipServerCfgEntry OBJECT-TYPE    
       SYNTAX     SipServerCfgEntry    
       MAX-ACCESS not-accessible    
       STATUS     current    
       DESCRIPTION    
            "A row of common configuration.  
  
             Each row represents those objects for a particular SIP   
             server present in this system.  applIndex is used to   
             uniquely identify these instances of SIP servers and   
             correlate them through the common framework of the   
             NETWORK-SERVICES-MIB (RFC 2788). The same value of  
             applIndex used in the corresponding SIP-COMMON-MIB 
             is used here."  
       INDEX { applIndex }    
       ::= { sipServerCfgTable 1 }    
       
   SipServerCfgEntry ::=    
       SEQUENCE {    
                sipServerHostAddrType           InetAddressType,    
                sipServerHostAddr               InetAddress,  
                sipPgpVersion                   SnmpAdminString,    
                sipServerContactDfltAction      INTEGER,    
                sipServerRespectUAAction        TruthValue    
       }    
       
   sipServerHostAddrType OBJECT-TYPE    
       SYNTAX     InetAddressType  
       MAX-ACCESS read-write    
       STATUS     current    
       DESCRIPTION    
            "The type of 
             is reachable."  
       REFERENCE    
             "RFC 2543, Section 2"    
     
   

   
    
       ::= { sipServerCfgEntry 1 }    
     
   sipServerHostAddr OBJECT-TYPE    
       SYNTAX     InetAddress (SIZE(1..254))  
       MAX-ACCESS read-write    
       STATUS     current    
       DESCRIPTION    
            "This is the host portion of a SIP URL that is assigned    
             to the SIP server.  It may contain a fully qualified    
             domain name, or an IP address.  The length of the value  
             will depend on the type of address specified.    
             sipServerHostAddrType formalizes the type of address  
             given by this object.  It is the users responsibility  
             to maintain consistency between this object and the  
             type specified by sipServerHostAddrType."  
       REFERENCE    
             "RFC 2543, Section 2"    
       ::= { sipServerCfgEntry 2 }    
       
   --    
   -- Security    
   --    
   sipPgpVersion OBJECT-TYPE    
       SYNTAX     SnmpAdminString    
       MAX-ACCESS read-only    
       STATUS     current    
       DESCRIPTION    
            "This object indicates the version of PGP (Pretty Good    
             Privacy) supported by this server.  Common values are    
             2.6.2 and 5.0."    
       ::= { sipServerCfgEntry 3 }    
       
   --    
   -- Additional Server Configuration    
   --   
   sipServerContactDfltAction OBJECT-TYPE    
       SYNTAX     INTEGER {   
                          redirect(1),    
                          proxy(2)   
                  }   
       MAX-ACCESS read-write    
       STATUS     current    
       DESCRIPTION    
            "This object specifies whether the default contact action    
             of the server is to be a proxy or a redirect server.  A    
             User Agent may indicate a preference upon registration of    
             Contact information. The value of this object is used in    
             the absence of such an indication."    
       REFERENCE    
             "RFC 2543,  Section 6.13"    
       ::= { sipServerCfgEntry 4 }    
       
   sipServerRespectUAAction OBJECT-TYPE    
       SYNTAX     TruthValue    
       MAX-ACCESS read-write    
       STATUS     current    
       DESCRIPTION    
     
   

   
    
            "This object specifies whether the server should respect    
             the wishes of a User Agent when the UA specifies a server    
             action (proxy or redirect) for certain Contact    
             information.  If the value of this object is false, then    
             the value contained in the sipServerContactDfltAction   
             is used."    
       REFERENCE    
             "RFC 2543, Section 6.13"    
       ::= { sipServerCfgEntry 5 }    
       
   --   
   -- This group contains MIB objects related to SIP Proxy Servers.    
   --    
   sipProxyCfg      OBJECT IDENTIFIER ::= { sipServerMIBObjects 3 }  
   sipProxyStats    OBJECT IDENTIFIER ::= { sipServerMIBObjects 4 }  
       
   --    
   -- Proxy Server Configuration    
   --    
   sipProxyCfgTable OBJECT-TYPE    
       SYNTAX     SEQUENCE OF SipProxyCfgEntry    
       MAX-ACCESS not-accessible    
       STATUS     current    
       DESCRIPTION    
            "This table contains configuration objects applicable    
             to SIP proxy servers."  
       ::= { sipProxyCfg 1 }    
       
   sipProxyCfgEntry OBJECT-TYPE    
       SYNTAX     SipProxyCfgEntry    
       MAX-ACCESS not-accessible    
       STATUS     current    
       DESCRIPTION    
            "A row of common proxy configuration.  
  
             Each row represents those objects for a particular SIP   
             server present in this system.  applIndex is used to   
             uniquely identify these instances of SIP servers and   
             correlate them through the common framework of the   
             NETWORK-SERVICES-MIB (RFC 2788).  The same value of 
             applIndex used in the corresponding SIP-COMMON-MIB  
             is used here."  
       INDEX { applIndex }    
       ::= { sipProxyCfgTable 1 }    
       
   SipProxyCfgEntry ::=    
       SEQUENCE {    
                sipRequestMaxExpires         Unsigned32,    
                sipProxyStatefulness         INTEGER,    
                sipProxySendsCancel          TruthValue,    
                sipProxyForwardAll1xx        TruthValue,    
                sipProxyRecursion            TruthValue,    
                sipProxyProvideAlternatives  TruthValue,    
                sipProxyRecordRoute          TruthValue,    
                sipProxyStateTimeout         Integer32,    
                sipProxyAuthMethod           BITS,    
                sipProxyAuthPgpAlgorithm     INTEGER,    
     
   

   
    
                sipProxyAuthRealm            SnmpAdminString,    
                sipProxyNonceLifeTime        Integer32,    
                sipPgpPrivateKey             OCTET STRING   
       }    
           
   sipRequestMaxExpires OBJECT-TYPE    
       SYNTAX     Unsigned32 (0..4294967295)    
       UNITS      "seconds"    
       MAX-ACCESS read-write    
       STATUS     current    
       DESCRIPTION    
            "This object specifies the maximum duration that a SIP    
             proxy server will accept from a client in the Expires    
             header."  
       ::= { sipProxyCfgEntry 1 }    
       
   sipProxyStatefulness OBJECT-TYPE    
       SYNTAX     INTEGER {  
                           stateless(1),  
                           transactionStateful(2),  
                           callStateful(3)  
                   }  
       MAX-ACCESS read-write    
       STATUS     current    
       DESCRIPTION    
            "This object specifies the default mode of operation for  
             the proxy server entity.  
  
             A stateless proxy entity does not maintain state  
             for a SIP transaction. A stateless proxy forwards every  
             request it receives downstream and every response it  
             receives upstream.   If the value of this object is   
             stateless(1), the proxy defaults to stateless operations.  
  
             A transaction stateful proxy, or simply a 'stateful  
             proxy', maintains state information for the duration of  
             a SIP transaction.  If the value if this object is  
             transactionStateful(2), the proxy is stateful on a  
             transaction basis.  
  
             A call stateful proxy does retain state that persists  
             for the duration of a call initiated through it. To  
             properly manage that state, the proxy will normally  
             need to receive the BYE requests that terminate the call.  
             If the value of this object is callStateful(3), the   
             proxy is call stateful."  
       REFERENCE    
             "RFC 2543, Section 12.3"    
       ::= { sipProxyCfgEntry 2 }    
       
   sipProxySendsCancel OBJECT-TYPE    
       SYNTAX     TruthValue    
       MAX-ACCESS read-write    
       STATUS     current    
       DESCRIPTION    
            "This object specifies whether or not a forking proxy sends    
             CANCEL on outstanding branch requests after receiving a    
     
   

   
    
             2xx or 6xx, or after the request times-out.    
       
             If the value of this object is true, the server sends a    
             CANCELs on branches where no definitive response has been    
             received.  If false, the proxy does not send CANCELs."    
       REFERENCE    
             "RFC 2543, Section 12.4"    
       ::= { sipProxyCfgEntry 3 }    
       
       
   sipProxyForwardAll1xx OBJECT-TYPE    
       SYNTAX     TruthValue    
       MAX-ACCESS read-write    
       STATUS     current    
       DESCRIPTION    
            "This object specifies whether or not the proxy forwards    
             all 1xx responses, except the 100 Trying response,     
             upstream towards the source of the request.    
       
             If the value of this object is true, the 1xx responses are    
             sent.  If the value is false, duplicate 1xx responses are    
             not sent upstream."    
       ::= { sipProxyCfgEntry 4 }    
       
   sipProxyRecursion OBJECT-TYPE    
       SYNTAX     TruthValue    
       MAX-ACCESS read-write    
       STATUS     current    
       DESCRIPTION    
            "This object specifies whether or not the Proxy performs    
             recursive search on the Contacts provided in 3xx    
             redirects.    
       
             If the value of this object is true, a recursive search is    
             performed.  If the value is false, no search is performed,    
             the 3xx response is sent upstream towards the source of    
             the request."    
       ::= { sipProxyCfgEntry 5 }    
       
   sipProxyProvideAlternatives OBJECT-TYPE    
       SYNTAX     TruthValue    
       MAX-ACCESS read-write    
       STATUS     current    
       DESCRIPTION    
            "The object specifies whether or not the Server provides    
             alternative Contacts in 3xx and 485 responses.    
       
             If the value of this object is true, the server inserts a    
             list of alternative URLs into a Contact header where the    
             request Originator may possibly find the desired called    
             party.  If the value is false, the server doesn't add    
             Contact information to 3xx and 485 responses.    
       
             Note that the policies of a server may limit the    
             particular alternatives that are returned when this object    
             is set to true."    
       REFERENCE    
     
   

   
    
             "RFC 2543, Section 6.13"    
       DEFVAL { false }    
       ::= { sipProxyCfgEntry 6 }    
       
   sipProxyRecordRoute OBJECT-TYPE    
       SYNTAX     TruthValue    
       MAX-ACCESS read-write    
       STATUS     current    
       DESCRIPTION    
            "This object specifies whether or not the proxy adds itself    
       
             to the Record-Route header as a default action.  This     
             header is used to list the proxies that insist on being in    
             the signalling path for subsequent requests related to the     
             call-leg.    
       
             If the value of this object is true, the proxy adds itself    
             to the end of the Record-Route header, creating the header    
             if required.  If the value is false, the proxy doesn't add     
             itself to the Record-Route header."    
       REFERENCE    
             "RFC 2543, Section 6.29"    
       ::= { sipProxyCfgEntry 7 }    
       
   sipProxyStateTimeout OBJECT-TYPE    
       SYNTAX     Integer32 (0..255)    
       UNITS      "seconds"    
       MAX-ACCESS read-write    
       STATUS     current    
       DESCRIPTION    
            "This object specifies the duration after reception of the    
             first INVITE response that a stateful proxy retains state   
             in order to handle possible retransmissions of the  
             response."    
       REFERENCE    
             "RFC 2543, Section 12.3.6"    
       ::= { sipProxyCfgEntry 8 }    
       
   --    
   -- Security    
   --    
   sipProxyAuthMethod OBJECT-TYPE    
       SYNTAX     BITS {    
                          none(0),    
                          basic(1),    
                          digest(2),    
                          pgp(3)    
                  }    
       MAX-ACCESS read-write    
       STATUS     current    
       DESCRIPTION    
            "This object specifies the authentication method that is    
             used to authenticate request originators.   
   
             bit 0  no authentication is performed   
             bit 1  HTTP basic is used   
             bit 2  HTTP digest is used   
     
   

   
    
             bit 3  PGP (Pretty Good Privacy) is used."   
       ::= { sipProxyCfgEntry 9 }    
       
   sipProxyAuthPgpAlgorithm OBJECT-TYPE    
       SYNTAX     INTEGER {    
                          other(1),    
                          md5(2),    
                          sha1(3)    
       
                  }    
       MAX-ACCESS read-write    
       
       STATUS     current    
       DESCRIPTION    
            "This object specifies the PGP algorithm the proxy uses."    
       ::= { sipProxyCfgEntry 10 }    
       
   sipProxyAuthRealm OBJECT-TYPE    
       SYNTAX     SnmpAdminString    
       MAX-ACCESS read-write    
       STATUS     current    
       DESCRIPTION    
            "This object specifies the realm used in Proxy-Authenticate    
             headers.  Note that this may need to be stored per user."    
       ::= { sipProxyCfgEntry 11 }    
       
   sipProxyNonceLifeTime OBJECT-TYPE    
       SYNTAX Integer32 (0..65535)    
       UNITS "milliseconds"    
       MAX-ACCESS read-write    
       STATUS current    
       DESCRIPTION    
            "This object specifies the life-time of a given nonce.  A    
             nonce is a server specified value whose contents are    
             opaque to the entity being authenticated and which is used    
             in calculating authentication data.  If this object has a    
             value of zero, then    
             nonces are not reused."    
       ::= { sipProxyCfgEntry 12 }    
       
   --    
   -- Proxy-Authenticate received by this server    
   -- (i.e. this server is being authenticated by a peer)    
   --    
   sipPgpPrivateKey OBJECT-TYPE    
       SYNTAX     OCTET STRING(SIZE(0..255))    
       MAX-ACCESS read-write    
       STATUS     current    
       DESCRIPTION    
            "The value of this object is the server's private PGP key,    
             used for both PGP authentication of this server and for    
             PGP-based    
             encryption."    
       ::= { sipProxyCfgEntry 13 }    
       
 
 
     
   

   
    
   --    
   -- Proxy Server Statistics    
   --    
   sipProxyStatsTable OBJECT-TYPE    
       SYNTAX     SEQUENCE OF SipProxyStatsEntry    
       MAX-ACCESS not-accessible    
       STATUS     current    
       DESCRIPTION    
            "This table contains the statistics objects applicable    
             to all SIP Proxy Servers in this system."  
       ::= { sipProxyStats 1 }    
       
   sipProxyStatsEntry OBJECT-TYPE    
       SYNTAX     SipProxyStatsEntry    
       MAX-ACCESS not-accessible    
       STATUS     current    
       DESCRIPTION    
            "A row of summary statistics.  
  
             Each row represents those objects for a particular SIP   
             server present in this system.  applIndex is used to   
             uniquely identify these instances of SIP servers and   
             correlate them through the common framework of the   
             NETWORK-SERVICES-MIB (RFC 2788).  The same value of  
             applIndex used in the corresponding SIP-COMMON-MIB 
             is used here."  
       INDEX { applIndex }    
       ::= { sipProxyStatsTable 1 }    
       
   SipProxyStatsEntry ::=    
       SEQUENCE {    
                sipNumProxyRequireFailures Counter32    
       }    
       
   sipNumProxyRequireFailures OBJECT-TYPE    
       SYNTAX     Counter32    
       MAX-ACCESS read-only    
       STATUS     current    
       DESCRIPTION    
            "This object contains the number of occurrences of    
             unsupported options being specified in received Proxy-    
             Require headers.  Such occurrences result in a 420 Bad    
             Extension status code being    
             returned."    
       ::= { sipProxyStatsEntry 1 }    
       
   --    
   -- This group contains MIB objects related to SIP Redirect Servers.    
   --    
   sipRedirCfg            OBJECT IDENTIFIER ::= { sipServerMIBObjects 5  
}  
   sipRedirStats          OBJECT IDENTIFIER ::= { sipServerMIBObjects 6  
}    
       
   -- none at this time    
   
   --    
     
   

   
    
   -- This group contains MIB objects related to SIP Registrars.    
   --    
   sipRegCfg              OBJECT IDENTIFIER ::= { sipServerMIBObjects 7  
}  
   sipRegStats            OBJECT IDENTIFIER ::= { sipServerMIBObjects 8  
}  
       
   --    
   -- Registrar Configuration    
   --    
   sipRegCfgTable OBJECT-TYPE    
       SYNTAX     SEQUENCE OF SipRegCfgEntry    
       MAX-ACCESS not-accessible    
       STATUS     current    
       DESCRIPTION    
            "This table contains configuration objects applicable    
             SIP registrars."  
       ::= { sipRegCfg 1 }    
       
   sipRegCfgEntry OBJECT-TYPE    
       SYNTAX     SipRegCfgEntry    
       MAX-ACCESS not-accessible    
       STATUS     current    
       DESCRIPTION    
            "A row of common registrar configuration.  
  
             Each row represents those objects for a particular SIP   
             server present in this system.  applIndex is used to   
             uniquely identify these instances of SIP servers and   
             correlate them through the common framework of the   
             NETWORK-SERVICES-MIB (RFC 2788). The same value of  
             applIndex used in the corresponding SIP-COMMON-MIB 
             is used here."  
       INDEX { applIndex }    
       ::= { sipRegCfgTable 1 }    
       
   SipRegCfgEntry ::=    
       SEQUENCE {    
                sipRegAllowThirdParty           TruthValue,    
                sipRegMaxContactExpiryDate      Unsigned32,    
                sipRegMaxUsers                  Unsigned32,    
                sipRegCurrentUsers              Gauge32,    
                sipRegDfltRegActiveInterval     Unsigned32   
       }    
       
   sipRegAllowThirdParty OBJECT-TYPE    
       SYNTAX     TruthValue    
       MAX-ACCESS read-write    
       STATUS     current    
       DESCRIPTION    
            "This object specifies whether or not the Registrar should    
             allows third party registrations. In third-party  
             registration, the entity issuing the request (in the From  
             header) is different from the entity being registered (in  
             the To header) to whom the provided Contact information 
             applies.    
                
     
   

   
    
             If the value of this object is true, the Registrar allows    
             third party registrations.  If the value is false, third    
             party registrations are rejected: a 403 Forbidden status    
             code is returned to the requestor."    
       REFERENCE    
            "RFC 2543, Section 4.2.6"    
       ::= { sipRegCfgEntry 1 }    
       
   sipRegMaxContactExpiryDate OBJECT-TYPE    
       SYNTAX     Unsigned32 (0..4294967295)    
       UNITS      "seconds"    
       MAX-ACCESS read-write    
       STATUS     current    
       DESCRIPTION    
            "This object specifies the maximum expiry that may be    
             requested by a User Agent for a particular Contact.  User    
             Agents can specify expiry using either an Expiry header in    
             a REGISTER request, or using an Expires parameter in a    
             Contact header in a REGISTER request.  If the value    
             requested by the User Agent is greater than the value of    
             this object, then the contact information is given the    
             duration specified by this object, and that duration    
             is indicated to the User Agent in the response."    
       DEFVAL { 4294967295 }    
       ::= { sipRegCfgEntry 2 }    
       
   sipRegMaxUsers OBJECT-TYPE    
       SYNTAX     Unsigned32 (1..4294967295)    
       MAX-ACCESS read-only    
       STATUS     current    
       DESCRIPTION    
            "This object specifies the maximum number of users that the    
             registrar supports.  The current number of users is    
             reflected by sipRegCurrentUsers."    
       ::= { sipRegCfgEntry 3 }    
       
   sipRegCurrentUsers OBJECT-TYPE    
       SYNTAX     Gauge32 (0..4294967295)    
       MAX-ACCESS read-only    
       STATUS     current    
       DESCRIPTION    
            "This object specifies the number of users currently    
             configured on the registrar."    
       ::= { sipRegCfgEntry 4 }    
   
   sipRegDfltRegActiveInterval OBJECT-TYPE    
       SYNTAX     Unsigned32 (1..4294967295)   
       UNITS      "seconds"   
       MAX-ACCESS read-write   
       STATUS     current    
       DESCRIPTION    
            "This object specifies the default time interval the   
             Registrar considers registrations to be active.  The   
             value is used to compute the Expires header in the   
             REGISTER response.  If a user agent requests a time   
             interval shorter than specified by this object, the   
             Registrar should honor that request.  If a Contact   
     
   

   
    
             entry does not have an 'expires' parameter, this  
             object is used as the default value."   
       REFERENCE "Expires header, section 6.20 RFC2543"   
       ::= { sipRegCfgEntry 5 }    
   
   --    
   -- Per User Information    
   --    
   sipRegUserTable OBJECT-TYPE    
       SYNTAX     SEQUENCE OF SipRegUserEntry    
       MAX-ACCESS not-accessible    
       STATUS     current    
       DESCRIPTION    
            "This table contains information on all users registered to    
             each Registrar in this system."  
       ::= { sipRegCfg 2 }    
       
   sipRegUserEntry OBJECT-TYPE    
       SYNTAX     SipRegUserEntry    
       MAX-ACCESS not-accessible    
       STATUS     current    
       DESCRIPTION    
            "This entry contains information for a single user    
             registered to this Registrar.  
  
             Each row represents those objects for a particular SIP   
             server present in this system.  applIndex is used to   
             uniquely identify these instances of SIP servers and   
             correlate them through the common framework of the   
             NETWORK-SERVICES-MIB (RFC 2788).  The same value of 
             applIndex used in the corresponding SIP-COMMON-MIB 
             is used here."  
       INDEX { applIndex, sipUserIndex }    
       ::= { sipRegUserTable 1 }    
       
   SipRegUserEntry ::=    
       SEQUENCE {    
                sipUserIndex                         Unsigned32,    
                sipUserUri                           SnmpAdminString,    
                sipUserAuthenticationFailures        Counter32,    
                sipUserTableRowStatus                RowStatus    
       }    
       
   sipUserIndex OBJECT-TYPE    
       SYNTAX     Unsigned32 (1..4294967295)    
       MAX-ACCESS not-accessible    
       STATUS     current    
       DESCRIPTION    
            "This object uniquely identifies a conceptual row in the    
             table."    
       ::= { sipRegUserEntry 1 }    
       
   sipUserUri OBJECT-TYPE    
       SYNTAX     SnmpAdminString    
       MAX-ACCESS read-create    
       STATUS     current    
       DESCRIPTION    
     
   

   
    
            "This object contains the user's address-of-record.  It is    
             the main form by which the registrar knows the user.  The    
             format is typically 'user@domain'.  It is contained in the    
             To header for all REGISTER requests."    
       ::= { sipRegUserEntry 2 }    
       
   sipUserAuthenticationFailures OBJECT-TYPE    
       SYNTAX     Counter32    
       MAX-ACCESS read-only    
       STATUS     current    
       DESCRIPTION    
            "This object contains a count of the number of times the    
             user has failed authentication."    
       ::= { sipRegUserEntry 3 }    
       
   sipUserTableRowStatus OBJECT-TYPE    
       SYNTAX     RowStatus    
       MAX-ACCESS read-create    
       STATUS     current    
       DESCRIPTION    
            "The row status of the entry. This object is required    
             to create or delete rows remotely by a manager."    
       ::= { sipRegUserEntry 4 }    
       
   --    
   -- Per Contact Information    
   --    
   sipContactTable OBJECT-TYPE    
       SYNTAX     SEQUENCE OF SipContactEntry    
       MAX-ACCESS not-accessible    
       STATUS     current    
       DESCRIPTION    
            "This table contains information on every location where a    
             registered user (specified by sipUserIndex) wishes to be     
             found (i.e. the user has provided Contact information to    
             each SIP Registrar in this system)."  
       ::= { sipRegCfg 3 }    
       
   sipContactEntry OBJECT-TYPE    
       SYNTAX     SipContactEntry    
       MAX-ACCESS not-accessible    
       STATUS     current    
       DESCRIPTION    
            "This entry contains information for a single Contact.    
             Multiple contacts may exist for a single user.  
  
             Each row represents those objects for a particular SIP   
             server present in this system.  applIndex is used to   
             uniquely identify these instances of SIP servers and   
             correlate them through the common framework of the   
             NETWORK-SERVICES-MIB (RFC 2788).  The same value of  
             applIndex used in the corresponding SIP-COMMON-MIB  
             is used here."  
       INDEX { applIndex, sipUserIndex, sipContactIndex }    
       ::= { sipContactTable 1 }    
       
 
     
   

   
    
   SipContactEntry ::=    
       SEQUENCE {    
                sipContactIndex                Unsigned32,    
                sipContactDisplayName          SnmpAdminString,    
                sipContactURI                  SnmpAdminString,    
                sipContactLastUpdated          TimeStamp,    
                sipContactExpiry               DateAndTime,    
                sipContactPreference           SnmpAdminString, 
                sipContactAction               INTEGER,    
                sipContactRetryAfter           DateAndTime    
       }    
       
   sipContactIndex OBJECT-TYPE    
       SYNTAX     Unsigned32 (1..4294967295)    
       MAX-ACCESS not-accessible    
       STATUS     current    
       DESCRIPTION    
            "Along with the sipUserIndex, this object uniquely    
             identifies a conceptual row in the table."    
       ::= { sipContactEntry 1 }    
       
   sipContactDisplayName OBJECT-TYPE    
       SYNTAX     SnmpAdminString    
       MAX-ACCESS read-only    
       STATUS     current    
       DESCRIPTION    
            "This object contains the display name for the Contact.    
             For example, 'Santa at Home', or 'Santa on his Sled',    
             corresponding to contact URLs of    
             sip:BigGuy@sip.northpole.ca or    
             sip:sclaus817@sip.mobile.com, respectively."    
       ::= { sipContactEntry 2 }    
       
   sipContactURI OBJECT-TYPE    
       SYNTAX     SnmpAdminString    
       MAX-ACCESS read-only    
       STATUS     current    
       DESCRIPTION    
            "This object contains either a SIP URL or a URI where the    
             user can be contacted.  This URI is normally returned to a    
             client from a redirect server, or is used as the    
             RequestURI in a SIP request line for requests forwarded by    
             a proxy."    
       ::= { sipContactEntry 3 }    
       
   sipContactLastUpdated OBJECT-TYPE    
       SYNTAX     TimeStamp    
       MAX-ACCESS read-only    
       STATUS     current    
       DESCRIPTION    
            "This object indicates the time when this contact    
             information was accepted.  If the contact information is    
             updated via a subsequent REGISTER of the same information,    
             this object is also updated."    
       ::= { sipContactEntry 4 }    
       
   sipContactExpiry OBJECT-TYPE    
     
   

   
    
       SYNTAX     DateAndTime    
       MAX-ACCESS read-only    
       STATUS     current    
       DESCRIPTION    
            "This object contains the date and time when the contact    
       
             information will no longer be valid.  Such times may be    
             specified by the user at registration (Expires header or    
             expiry parameter in the Contact information), or a system    
             default can be applied."    
       ::= { sipContactEntry 5 }    
       
   sipContactPreference OBJECT-TYPE    
       SYNTAX     SnmpAdminString 
       MAX-ACCESS read-only    
       STATUS     current    
       DESCRIPTION    
            "This object specifies the preference for this contact    
             relative to all other active contacts for same user.  A    
             registering user may provide this preference as a 'qvalue'    
             parameter in the Contact header.    
       
             The format of this item is a decimal number between 0    
             and 1 (for example 0.9).  Higher values indicate locations    
             preferred by the user."    
       REFERENCE    
            "RFC 2543, Section 6.13"    
       ::= { sipContactEntry 6 }    
       
   sipContactAction OBJECT-TYPE    
       SYNTAX     INTEGER {   
                          redirect(1),    
                          proxy(2)   
                  }   
       MAX-ACCESS read-only    
       STATUS     current    
       DESCRIPTION    
            "This object indicates whether the user wanted the server    
             to act as a redirect server or as a proxy server.  It is    
             specified by the optional 'action' parameter in the    
             Contact header."    
       ::= { sipContactEntry 7 }    
       
   sipContactRetryAfter OBJECT-TYPE    
       SYNTAX     DateAndTime    
       MAX-ACCESS read-only    
       STATUS     current    
       DESCRIPTION    
            "This object indicates that the contact information is    
             currently inactive, and that it should only be activated    
             after the date and time specified by the object.  This    
             value is provided by a user when deleting contact    
             information using a REGISTER request containing a Retry-    
             After header."    
       REFERENCE    
            "RFC 2543, Section 6.32"    
       ::= { sipContactEntry 8 }    
     
   

   
    
       
       
   --    
   -- Registrar Statistics    
   --    
   sipRegStatsTable OBJECT-TYPE    
       SYNTAX     SEQUENCE OF SipRegStatsEntry    
       MAX-ACCESS not-accessible    
       STATUS     current    
       DESCRIPTION    
            "This table contains the summary statistics objects    
             applicable to all SIP Registrars in this system."  
       ::= { sipRegStats 1 }    
       
   sipRegStatsEntry OBJECT-TYPE    
       SYNTAX     SipRegStatsEntry    
       MAX-ACCESS not-accessible    
       STATUS     current    
       DESCRIPTION    
            "A row of summary statistics.  
  
             Each row represents those objects for a particular SIP   
             server present in this system.  applIndex is used to   
             uniquely identify these instances of SIP servers and   
             correlate them through the common framework of the   
             NETWORK-SERVICES-MIB (RFC 2788).  The same value of  
             applIndex used in the corresponding SIP-COMMON-MIB  
             is used here."  
       INDEX { applIndex }    
       ::= { sipRegStatsTable 1 }    
       
   SipRegStatsEntry ::=    
       SEQUENCE {    
                sipRegAcceptedRegistrations Counter32,    
                sipRegRejectedRegistrations Counter32    
       }    
       
   sipRegAcceptedRegistrations OBJECT-TYPE    
       SYNTAX     Counter32    
       MAX-ACCESS read-only    
       STATUS     current    
       DESCRIPTION    
            "This object contains a count of the number of REGISTER    
             requests that have been accepted (status code 200) by the    
             Registrar.  This includes additions of new contact    
             information, refreshing contact information, as well as    
             requests for deletion of contact information."    
       ::= { sipRegStatsEntry 1 }    
       
   sipRegRejectedRegistrations OBJECT-TYPE    
       SYNTAX     Counter32    
       MAX-ACCESS read-only    
       STATUS     current    
       DESCRIPTION    
            "This object contains a count of the number REGISTER    
             requests that have been rejected by the Registrar."    
       ::= { sipRegStatsEntry 2 }    
     
   

   
    
       
   --    
   -- Conformance    
   --    
   sipServerMIBCompliances          
     OBJECT IDENTIFIER ::= { sipServerMIBConform 1 }    
   sipServerMIBGroups               
     OBJECT IDENTIFIER ::= { sipServerMIBConform 2 }    
       
   --    
   -- Compliance Statements    
   --    
   sipProxyServerCompliance MODULE-COMPLIANCE    
       STATUS     current    
       DESCRIPTION    
            "The compliance statement for SIP entities acting   
             as proxy servers."    
       MODULE -- this module    
            MANDATORY-GROUPS { sipServerConfigGroup,   
                               sipProxyConfigGroup,   
                               sipProxyStatsGroup }   
       ::= { sipServerMIBCompliances 1 }    
   
   sipRedirectServerCompliance MODULE-COMPLIANCE    
       STATUS     current    
       DESCRIPTION    
            "The compliance statement for SIP entities acting   
             as redirect servers."    
       MODULE -- this module    
            MANDATORY-GROUPS { sipServerConfigGroup }   
       ::= { sipServerMIBCompliances 2 }    
       
   sipRegistrarServerCompliance MODULE-COMPLIANCE    
       STATUS     current    
       DESCRIPTION    
            "The compliance statement for SIP entities acting   
             as registrars."    
       MODULE -- this module    
            MANDATORY-GROUPS { sipServerConfigGroup,   
                               sipRegistrarConfigGroup,   
                               sipRegistrarStatsGroup }   
       ::= { sipServerMIBCompliances 3 }    
   
   --    
   -- Units of Conformance    
   --    
   sipServerConfigGroup OBJECT-GROUP    
       OBJECTS {    
               sipServerHostAddrType,    
               sipServerHostAddr,    
               sipPgpVersion,    
               sipServerContactDfltAction,    
               sipServerRespectUAAction    
       }    
       STATUS  current    
       DESCRIPTION    
            "A collection of objects providing configuration common    
     
   

   
    
             to SIP Proxy and Redirect servers."    
       ::= { sipServerMIBGroups 1 }    
       
   sipProxyConfigGroup OBJECT-GROUP    
       OBJECTS {    
               sipRequestMaxExpires,    
               sipProxyStatefulness,    
               sipProxySendsCancel,    
               sipProxyForwardAll1xx,    
               sipProxyRecursion,    
               sipProxyProvideAlternatives,    
               sipProxyRecordRoute,    
               sipProxyStateTimeout,    
               sipProxyAuthMethod,    
               sipProxyAuthPgpAlgorithm,    
               sipProxyAuthRealm,    
               sipProxyNonceLifeTime,    
               sipPgpPrivateKey  
       }    
       STATUS  current    
       DESCRIPTION    
            "A collection of objects providing configuration for    
             SIP Proxy servers."    
       ::= { sipServerMIBGroups 2 }    
       
   sipProxyStatsGroup OBJECT-GROUP    
       OBJECTS {    
               sipNumProxyRequireFailures    
       }    
       STATUS  current    
       DESCRIPTION    
            "A collection of objects providing statistics for    
             SIP Proxy servers."    
       ::= { sipServerMIBGroups 3 }    
       
   sipRegistrarConfigGroup OBJECT-GROUP    
       OBJECTS {    
               sipRegAllowThirdParty,    
               sipRegMaxContactExpiryDate,    
               sipRegMaxUsers,    
               sipRegCurrentUsers,    
               sipRegDfltRegActiveInterval,   
               sipUserUri,    
               sipUserAuthenticationFailures,    
               sipUserTableRowStatus,    
               sipContactDisplayName,    
               sipContactURI,    
               sipContactLastUpdated,    
               sipContactExpiry,    
               sipContactPreference,    
               sipContactAction,    
               sipContactRetryAfter    
       }    
       STATUS  current    
       DESCRIPTION    
            "A collection of objects providing configuration for    
             SIP Registrars."    
     
   

   
    
       ::= { sipServerMIBGroups 4 }   
       
   sipRegistrarStatsGroup OBJECT-GROUP    
       OBJECTS {    
               sipRegAcceptedRegistrations,    
               sipRegRejectedRegistrations    
       }    
       STATUS  current    
       DESCRIPTION    
            "A collection of objects providing statistics for    
             SIP Registrars."    
       ::= { sipServerMIBGroups 5 }   
   
   END
